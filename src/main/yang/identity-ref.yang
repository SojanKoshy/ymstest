module identity-ref {
    namespace "http://example.com/ns/idref/1.0";
    prefix idref;

    identity baseid;
    identity id {
        base baseid;
    }

    typedef my-type {
        type identityref {
            base baseid;
        }
    }

    container c {
        leaf ref-leaf {
            type my-type;
        }
        leaf-list llist {
            type decimal64 {
                fraction-digits 2;
            }
        }
        container child-container {
            container ch2;
        }
        list child-list {
            key "k i";
            leaf k {
                type string;
            }
            leaf i {
                type int32;
            }
        }
    }
}
