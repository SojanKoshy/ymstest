module topology { 
	yang-version 1;
    namespace urn:topo;
    prefix topo;
    revision 2014-01-01 {
        description "desc";
        reference "ref";
    }
    list node {
    	key "node-id";
    	leaf node-id{
           type string;
        }
        leaf-list node-prop{
           type string;
        }
        container termination-points{
            leaf number-of-tp {
                type int16;
            }
            list termination-point {
                key "tp-id";
                leaf tp-id {
                    type string;
                }
            }
        }
    }

    rpc set-node-limit {
        input {
            leaf node-limit {
                type int16;
            }
        }
    }

    notification node-limit-reached {
        leaf node-limit {
            type int16;
        }
    }
}
