module multiNotification {
  yang-version 1;
  namespace "urn:yms:test:ytb:multi:notification:with:container";
  prefix sch;

  revision 2016-08-26;

  notification linkDown {
    container router {
      leaf name {
        type string;
      }
    }
  }
  notification linkUp {
    container router {
      leaf name {
        type int32;
      }
    }
  }
}
