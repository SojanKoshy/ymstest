module root-module {
    namespace "root:module";
    prefix root;

    import imported-module { prefix imp; }
    
    //include submodule-1;
    include submodule-2;
    include submodule-to-submodule-1;

    typedef derived-union-type {
        type union {
            type int8;
            type string;
        }
    }

    

    typedef union-b {
        type union {
            type decimal64 {
                fraction-digits 2;
            }
            type boolean;
        }
    }

    typedef union-c {
        type union {
            type uint16 {
                range 10..20;
            }
            type string {
                pattern "a.*";
            }
        }
    }

    typedef union-d {
        type union {
            type uint16 {
                range 30..40;
            }
            type string {
                pattern "b.*";
            }
        }
    }

    typedef second-level-union {
        type union {
            type string;
            type uint32 {
                range 10..20;
            }
        }
    }

    typedef top-level-union {
        type union {
            type second-level-union;
            type uint32 {
                range 100..200;
            }
        }
    }

    container container {

        leaf u2 {
            type union {
                type string;
                type int8;
            }
            default "set from u2";
            description
                "A test leaf with a default";
        }

        leaf u3 {
            type union {
                type int8;
                type string;
            }
            default "set from u3";
            description
                "a test leaf with a default that must skip a type";
        }

        leaf u4 {
            type union {
                type int8;
                type string;
            }
            default 1;
            description
                "a test leaf that does not need to skip but is an int";
        }

        leaf u8 {
            type imp:derived-union-int-default;
            description
                "a test leaf with a typedef within a union";
        }

        leaf u1 {
            type union {
                type int8;
                type string;
            }
            description
                "A test leaf";
        }

        leaf u6 {
            type union {
                type uint8;
                type derived-string-type;
            }
        }

        leaf u7 {
            type derived-union-type;
        }

        leaf-list u9 {
            type union {
                type union-a;
                type union-b;
            }
        }

        leaf-list u10 {
            type union {
                type union-c;
                type union-d;
            }
        }

        leaf u11 {
            type top-level-union;
            default "string";
        }

        leaf u12 {
            type union {
                type enumeration {
                    enum unlimited;
                }
                type int16 {
                    range "0..max";
                }
            }
        }
    }

}
